# Launcher interface requirements, issue 2

# Specification: Launcher interface requirements

## 1: Scope

### 2
This module states the requirements the launch service places on a passenger satellite of up to 200 kg.
- Status: Agreed
- Verification Method: Review of Design

## 3: Mechanical interface

### 4
The satellite shall mate to the 15-inch separation system provided by the launch service.
- Status: Agreed
- Verification Method: Test

### 5
The satellite centre of mass shall lie within 25 mm of the separation axis.
- Status: Agreed
- Verification Method: Test, Analysis

### 6
The first lateral natural frequency shall be above 25 Hz with the satellite hard-mounted.
- Status: Agreed
- Verification Method: Test

### 7
The first axial natural frequency shall be above 45 Hz with the satellite hard-mounted.
- Status: Agreed
- Verification Method: Test

## 8: Environment

### 9: Mechanical environment

#### 10
The satellite shall withstand quasi-static loads of 8.5 g axial and 3.0 g lateral.
Loads are applied together, at the satellite centre of mass.
- Status: Agreed
- Verification Method: Analysis, Test
- satisfies -> 6

#### 11
The satellite shall withstand random vibration of 12.8 g rms, 20 to 2,000 Hz, 2 minutes per axis.
- Status: Agreed
- Verification Method: Test
- satisfies -> 6

#### 12
The satellite shall withstand a separation shock of 2,000 g SRS.
- Status: Agreed
- Verification Method: Test

### 13: Electromagnetic environment

#### 14
No satellite transmitter shall radiate until 45 minutes after separation.
- Status: Agreed
- Verification Method: Test, Review of Design
- satisfies -> 15

#### 15
Radiated emissions shall stay below the launcher susceptibility limits in the user manual, table 4-7.
- Status: Agreed
- Verification Method: Test

## 16: Safety

### 17
Each hazardous function shall be controlled by at least three independent inhibits.
- Status: Agreed
- Verification Method: Inspection

### 18
Pressure vessels shall be proof tested at 1.5 times their maximum expected operating pressure.
- Status: Agreed
- Verification Method: Test

### 19
The satellite shall be delivered with its battery below 30 % state of charge.
- Status: Deleted
- Verification Method: Inspection

### 20
Hydrazine loading shall be performed by the launch service's propellant team only.
- Status: Proposed
- Verification Method: Inspection
