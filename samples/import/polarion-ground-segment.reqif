# Ground segment requirements

# Specification: Ground Segment Requirements

## GS-100: Mission planning
- Type: heading

### GS-101: Plan generation
The planning system shall produce a conflict-free plan for the next 48 hours every 6 hours.
- Status: approved
- Severity: must_have
- Type: systemRequirement

### GS-102: Urgent tasking
An urgent request shall be planned in the next plan cycle, displacing routine tasks if needed.
- Status: approved
- Severity: must_have
- Type: systemRequirement
- depends_on -> GS-101

### GS-103: Plan upload
Each plan shall be uploaded at the first pass after it is generated.
- Status: reviewed
- Severity: must_have
- Type: systemRequirement
- depends_on -> GS-101

## GS-110: Data processing
- Type: heading

### GS-111: Level 1 products
Level 1C orthorectified products shall be produced within 2 hours of reception.
- Status: approved
- Severity: must_have
- Type: systemRequirement

### GS-112: Quality report
Each product shall carry a quality report with cloud cover and geolocation estimate.
- Status: draft
- Severity: should_have
- Type: systemRequirement

## GS-120: Operations security
- Type: heading

### GS-121: Two-factor login
Operators shall sign in with two-factor authentication.
- Status: approved
- Severity: must_have
- Type: systemRequirement

### GS-122: Command log
Every telecommand sent shall be logged with operator, time and pass.
- Status: approved
- Severity: must_have
- Type: systemRequirement

### GS-123: Session timeout
An idle operator session shall lock after 15 minutes.
- Status: draft
- Severity: nice_to_have
- Type: systemRequirement
