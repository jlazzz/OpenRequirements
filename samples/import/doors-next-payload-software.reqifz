# Payload software requirements

# Specification: Payload software requirements

## 41001: Acquisition
- Artifact Type: Heading

### 41002: Line rate control
The payload software shall set the detector line rate from the ground speed, between 1,200 and 2,000 lines per second.
- Artifact Type: Software Requirement
- Priority: High
- Planned In: R1.0

### 41003: Band selection
The payload software shall acquire any subset of the five bands, as commanded per imaging task.
- Artifact Type: Software Requirement
- Priority: Medium
- Planned In: R1.0

### 41004: Dark frames
The payload software shall record 256 dark lines with the shutter closed before every acquisition.
- Artifact Type: Software Requirement
- Priority: High
- Planned In: R1.0
- Elaborated By -> 41009

## 41005: Processing on board
- Artifact Type: Heading

### 41006: Compression
The payload software shall compress every band with CCSDS 122.0 at the commanded ratio.
- Artifact Type: Software Requirement
- Priority: High
- Planned In: R1.0

### 41007: Cloud flag
The payload software shall flag each scene with an estimated cloud fraction.
The estimate uses the blue and near-infrared bands only.
- Artifact Type: Software Requirement
- Priority: Low
- Planned In: R1.1, R2.0

## 41008: Health
- Artifact Type: Heading

### 41009: Detector temperature
The payload software shall stop an acquisition when the focal plane leaves 18 to 22 °C.
- Artifact Type: Software Requirement
- Priority: Medium
- Planned In: R1.0

### 41010: Event reporting
The payload software shall report every refused task with a reason code.
- Artifact Type: Software Requirement
- Priority: Low
- Planned In: R1.0
